module observer {
    namespace "urn:redbox:observer";
    prefix ov;

    revision 2021-12-10 {
        description "Initial revision.";
    }

    container config {
        description "Configuration container.";

        leaf config-value {
            description "A configuration value.";
            type uint32;
            default 0;
        }
    }
}
